FME workspace LandUseDataNormalization.fmw

Parameters:
- SourceDataset_ESRISHAPE = $(FME_MF_DIR)DataBank\StCatharines\Zoning.shp   # Source Esri Shapefile(s)
- DestDataset_GEODATABASE_FILE = $(FME_MF_DIR)Geodatabases\MRAnalyst.gdb   # File Geodatabase
- SourceDataset_ESRISHAPE_14 = $(FME_MF_DIR)DataBank\Welland2\Welland_current_zoning_by-law_2017-117.shp   # Source Esri Shapefile(s)
- DestDataset_GEODATABASE_FILE_5 = $(FME_MF_DIR)Geodatabases\MRAnalyst.gdb   # File Geodatabase
- SourceDataset_ESRISHAPE_17 = $(FME_MF_DIR)DataBank\NiagaraFalls\zoning-bylaw-1538-crowland.shp   # Source Esri Shapefile(s)
- SourceDataset_ESRISHAPE_21 = $(FME_MF_DIR)DataBank\NiagaraFalls\zoning-bylaw-7069-humberstone.shp   # Source Esri Shapefile(s)
- SourceDataset_ESRISHAPE_15 = $(FME_MF_DIR)DataBank\NiagaraFalls\zoning-bylaw-b0395-willoughby.shp   # Source Esri Shapefile(s)
- SourceDataset_ESRISHAPE_19 = $(FME_MF_DIR)DataBank\NiagaraFalls\New folder\zoning-bylaw-79-200.shp   # Source Esri Shapefile(s)
- SourceDataset_ESRISHAPE_23 = $(FME_MF_DIR)DataBank\Schools\Schools.shp   # Source Esri Shapefile(s)
- SourceDataset_ESRISHAPE_13 = $(FME_MF_DIR)DataBank\UrbanBoundaries\UAB.shp   # Source Esri Shapefile(s)
- SourceDataset_ESRISHAPE_16 = $(FME_MF_DIR)DataBank\NiagaraRegion\PublicTransitRoutes.shp   # Source Esri Shapefile(s)
- SourceDataset_ESRISHAPE_18 = $(FME_MF_DIR)DataBank\Grimsby\Zoning_14_45.shp   # Source Esri Shapefile(s)
- SourceDataset_ESRISHAPE_20 = $(FME_MF_DIR)DataBank\NiagaraRegion\MunicipalBoundaries.shp   # Source Esri Shapefile(s)
- SourceDataset_CSV2 = $(FME_MF_DIR)DataBank\NiagaraRegion\Demographics.csv   # Source CSV (Comma Separated Value) File(s)

Readers:
- ESRISHAPE_1: ESRISHAPE from $(SourceDataset_ESRISHAPE)
- ESRISHAPE_2: ESRISHAPE from $(SourceDataset_ESRISHAPE_14)
- ESRISHAPE_3: ESRISHAPE from $(SourceDataset_ESRISHAPE_17)
- ESRISHAPE_4: ESRISHAPE from $(SourceDataset_ESRISHAPE_21)
- ESRISHAPE_5: ESRISHAPE from $(SourceDataset_ESRISHAPE_15)
- ESRISHAPE_6: ESRISHAPE from $(SourceDataset_ESRISHAPE_19)
- ESRISHAPE_7: ESRISHAPE from $(SourceDataset_ESRISHAPE_23)
- ESRISHAPE_8: ESRISHAPE from $(SourceDataset_ESRISHAPE_13)
- ESRISHAPE_9: ESRISHAPE from $(SourceDataset_ESRISHAPE_16)
- ESRISHAPE_10: ESRISHAPE from $(SourceDataset_ESRISHAPE_18)
- ESRISHAPE_11: ESRISHAPE from $(SourceDataset_ESRISHAPE_20)
- CSV2_1: CSV2 from $(SourceDataset_CSV2)

Writers:
- GEODATABASE_FILE_1: GEODATABASE_FILE to $(DestDataset_GEODATABASE_FILE)
- GEODATABASE_FILE_2: GEODATABASE_FILE to $(DestDataset_GEODATABASE_FILE_5)
- ARCGISONLINEFEATURES_1: ARCGISONLINEFEATURES

Zoning_14_45 (reader ESRISHAPE_10)
    attributes: ZONECLASS char(10), ZONEDESC char(100), BASEELEV double, HEIGHT double, LASTUPDATE date, LASTEDITOR char(50), map char(254), new_zone char(254), MapTemp char(254), rural_labe char(254), Historical char(254), GRMID char(254), GlobalID char(38), SHAPE_STAr double, SHAPE_STLe double
    -> AttributeRenamer_10
AttributeRenamer_10
    ATTR_TABLE:
      RENAME_SET_DEFAULT ZONECLASS > LU_Code
      RENAME_SET_DEFAULT ZONEDESC > LU_Desc
    -> AttributeCreator_7
AttributeCreator_7
    ATTR_TABLE = SET_TO City = Grimsby
    -> AttributeKeeper_7
AttributeKeeper_7
    KEEP_ATTRS = City,LU_Code,LU_Desc
    -> AttributeManager_6
AttributeManager_6
    ATTR_TABLE:
      SET_TO LU_Code_alias = Landuse
      SET_TO LU_Desc_alias = Description
    -> CoordinateSystemSetter_8
CoordinateSystemSetter_8
    COORDSYS = EPSG:26917
    -> Agricultural
    -> Cemetry
    -> Commercial
    -> Commercial_3
    -> GrimsbyBeach
    -> Employment
    -> Residential
    -> Institutional
    -> Mixed
    -> Open_Space
    -> Rural
    -> Utility
    -> Neighbourhod_Development
Commercial_3: Tester
    BOOL_OP = OR
    TEST_CLAUSE:
      TEST @Value(LU_Code) = DI
      TEST @Value(LU_Code) = DMS
    PASSED -> Dissolver
Commercial: Tester
    BOOL_OP = OR
    TEST_CLAUSE:
      TEST @Value(LU_Code) = CC
      TEST @Value(LU_Code) = CS
      TEST @Value(LU_Code) = MC
      TEST @Value(LU_Code) = NC
      TEST @Value(LU_Code) = TRMC
    PASSED -> Dissolver
Agricultural: Tester
    BOOL_OP = OR
    TEST_CLAUSE = TEST @Value(LU_Code) = A
    PASSED -> Dissolver_2
Neighbourhod_Development: Tester
    BOOL_OP = OR
    TEST_CLAUSE = TEST @Value(LU_Code) = ND
Employment: Tester
    BOOL_OP = OR
    TEST_CLAUSE:
      TEST @Value(LU_Code) = GE
      TEST @Value(LU_Code) = PE
    PASSED -> Dissolver_3
GrimsbyBeach: Tester
    BOOL_OP = OR
    TEST_CLAUSE:
      TEST @Value(LU_Code) = GB
      TEST @Value(LU_Code) = DMS
Open_Space: Tester
    BOOL_OP = OR
    TEST_CLAUSE:
      TEST @Value(LU_Code) = O1
      TEST @Value(LU_Code) = O2
    PASSED -> Dissolver_5
Institutional: Tester
    BOOL_OP = OR
    TEST_CLAUSE = TEST @Value(LU_Code) = I
    PASSED -> Dissolver_6
Mixed: Tester
    BOOL_OP = OR
    TEST_CLAUSE = TEST @Value(LU_Code) = MHD
    PASSED -> MixedUse (writer GEODATABASE_FILE_1)
Residential: Tester
    BOOL_OP = OR
    TEST_CLAUSE:
      TEST @Value(LU_Code) = HR
      TEST @Value(LU_Code) = RD1
      TEST @Value(LU_Code) = RD2
      TEST @Value(LU_Code) = RD3
      TEST @Value(LU_Code) = RD4
      TEST @Value(LU_Code) = RD5
      TEST @Value(LU_Code) = RM1
      TEST @Value(LU_Code) = RM2
      TEST @Value(LU_Code) = RM3
      TEST @Value(LU_Code) = TRM
    PASSED -> Dissolver_8
Rural: Tester
    BOOL_OP = OR
    TEST_CLAUSE:
      TEST @Value(LU_Code) = RU
      TEST @Value(LU_Code) = SC
    PASSED -> AttributeKeeper_9
Utility: Tester
    BOOL_OP = OR
    TEST_CLAUSE = TEST @Value(LU_Code) = U
    PASSED -> AttributeKeeper_10
Cemetry: Tester
    BOOL_OP = OR
    TEST_CLAUSE = TEST @Value(LU_Code) = C
zoning-bylaw-1538-crowland (reader ESRISHAPE_3)
    attributes: ID number(18,0), OBJECTID number(18,0), B1538_ID number(18,0), BYLAW char(10), ZONE_ABR char(4), ZONE_TTL char(50), STREET char(25), LOCATION char(30), BYLAW_NO1 char(8), AMEND_NO1 char(8), SPEC_PROV1 char(8), BYLAW_NO2 char(8), AMEND_NO2 char(8), SPEC_PROV2 char(8), BYLAW_NO3 char(8), AMEND_NO3 char(8), ID2 number(18,0), Bylaw_No_L char(15), TypeI number(18,0), BranchesI number(18,0), Coordinate number(18,0), XI double, YI double, LongitudeI double, LatitudeI double, LengthI double, AreaI double, BearingI double, SelectionM number(18,0), SelectionI logical,
      VersionI number(18,0)
    -> CoordinateSystemSetter
CoordinateSystemSetter
    COORDSYS = EPSG:26917
    -> AttributeCreator_3
AttributeCreator_3
    ATTR_TABLE = SET_TO City = Niagara Falls
    -> AttributeKeeper_3
AttributeKeeper_3
    KEEP_ATTRS = ZONE_TTL,City,ZONE_ABR
    -> AttributeRenamer_2
AttributeRenamer_2
    ATTR_TABLE:
      RENAME_SET_DEFAULT ZONE_ABR > LU_Code
      RENAME_SET_DEFAULT ZONE_TTL > LU_Desc
    -> AttributeManager_9
AttributeManager_9
    ATTR_TABLE:
      SET_TO LU_Code_alias = Landuse
      SET_TO LU_Desc_alias = Description
    -> Tester_15
    -> Tester_12
    -> Tester_16
Tester_16
    BOOL_OP = OR
    TEST_CLAUSE = TEST @Value(LU_Code) = C2
    PASSED -> Dissolver
Tester_12
    BOOL_OP = OR
    TEST_CLAUSE = TEST @Value(LU_Code) = RA
    PASSED -> Dissolver_2
Tester_15
    BOOL_OP = OR
    TEST_CLAUSE = TEST @Value(LU_Code) = O2
    PASSED -> Dissolver_5
Zoning (reader ESRISHAPE_1)
    attributes: VALUE char(254), SHORT_VALU char(254), TEMP_ZONIN char(254)
    -> AttributeCreator_2
AttributeCreator_2
    ATTR_TABLE = SET_TO City = St. Catharines
    -> AttributeKeeper
AttributeKeeper
    KEEP_ATTRS = SHORT_VALU,VALUE,City
    -> AttributeRenamer
AttributeRenamer
    ATTR_TABLE:
      RENAME_SET_DEFAULT SHORT_VALU > LU_Code
      RENAME_SET_DEFAULT VALUE > LU_Desc
    -> AttributeManager_8
AttributeManager_8
    ATTR_TABLE:
      SET_TO LU_Code_alias = Landuse
      SET_TO LU_Desc_alias = Description
    -> Residential_2
    -> Mixed_Use
    -> Institutional_2
    -> Green_Space
    -> Conservation_Natural_Area
    -> General_Employment
    -> Agriculture
    -> Commercial_2
Institutional_2: Tester
    BOOL_OP = OR
    TEST_CLAUSE = CASE_INSENSITIVE_TEST @Value(LU_Code) CONTAINS I
    PASSED -> Dissolver_6
Residential_2: Tester
    BOOL_OP = OR
    TEST_CLAUSE = CASE_INSENSITIVE_TEST @Value(LU_Code) CONTAINS R
    PASSED -> Dissolver_8
Commercial_2: Tester
    BOOL_OP = OR
    TEST_CLAUSE = CASE_INSENSITIVE_TEST @Value(LU_Code) CONTAINS C
    PASSED -> Dissolver
Agriculture: Tester
    BOOL_OP = OR
    TEST_CLAUSE = CASE_INSENSITIVE_TEST @Value(LU_Code) CONTAINS A
    PASSED -> Dissolver_2
General_Employment: Tester
    BOOL_OP = OR
    TEST_CLAUSE = CASE_INSENSITIVE_TEST @Value(LU_Code) CONTAINS E
    PASSED -> Dissolver_3
Dissolver_3
    ACCUM_INPUT_ATTRS = Use Attributes From One Feature
    CLEANING_TOLERANCE = None
    CONNECT_Z_MODE = First Wins
    DEAGGREGATE_INPUT = Yes
    GROUP_BY = LU_Code
    NO_OVRLP = No
    AREA -> GeneralEmployment (writer GEODATABASE_FILE_1)
GeneralEmployment (writer GEODATABASE_FILE_1)
    attributes: LU_Code char(200), LU_Desc char(200), City char(200)
Conservation_Natural_Area: Tester
    BOOL_OP = OR
    TEST_CLAUSE = CASE_INSENSITIVE_TEST @Value(LU_Code) = G1
    PASSED -> Dissolver_4
Dissolver_4
    ACCUM_INPUT_ATTRS = Use Attributes From One Feature
    CLEANING_TOLERANCE = None
    CONNECT_Z_MODE = First Wins
    DEAGGREGATE_INPUT = Yes
    GROUP_BY = LU_Desc
    NO_OVRLP = No
    AREA -> ConservationNaturalArea (writer GEODATABASE_FILE_1)
ConservationNaturalArea (writer GEODATABASE_FILE_1)
    attributes: LU_Code char(200), LU_Desc char(200), City char(200)
Green_Space: Tester
    BOOL_OP = OR
    TEST_CLAUSE:
      CASE_INSENSITIVE_TEST @Value(LU_Code) = G2
      TEST @Value(LU_Code) = G3
    PASSED -> Dissolver_5
Mixed_Use: Tester
    BOOL_OP = OR
    TEST_CLAUSE = CASE_INSENSITIVE_TEST @Value(LU_Code) CONTAINS M
    PASSED -> MixedUse (writer GEODATABASE_FILE_1)
MixedUse (writer GEODATABASE_FILE_1)
    attributes: LU_Code char(200), LU_Desc char(200), City char(200)
zoning-bylaw-b0395-willoughby (reader ESRISHAPE_5)
    attributes: ID number(18,0), OBJECTID number(18,0), B0395_ID number(18,0), BYLAW char(9), ZONE_ABR char(4), ZONE_TTL char(35), STREET char(21), LOCATION char(28), BYLAW_NO1 char(8), AMEND_NO1 char(8), SPEC_PROV1 char(8), BYLAW_NO2 char(8), AMEND_NO2 char(8), SPEC_PROV2 char(8), BYLAW_NO3 char(8), AMEND_NO3 char(8), BYLAW_NO_L char(15), AdMapKey number(18,0), pID number(18,0), ppID number(18,0), New number(18,0), TEMP_EXPIR char(10), TypeI number(18,0), BranchesI number(18,0), Coordinate number(18,0), XI double, YI double, LongitudeI double, LatitudeI double, LengthI double,
      AreaI double, BearingI double, SelectionM number(18,0), SelectionI logical, VersionI number(18,0)
    -> CoordinateSystemSetter_2
CoordinateSystemSetter_2
    COORDSYS = EPSG:26917
    -> AttributeCreator_4
AttributeCreator_4
    ATTR_TABLE:
      SET_TO City = Niagara Falls
      SET_TO LU_Code = FME_CONDITIONAL:DEFAULT_VALUE'_FME_NO_OP_'BOOL_OP;OR;COMPOSITE_TEST;<Unused>;CASE_INSENSITIVE_TEST @Value(ZONE_TTL) CONTAINS OPEN SPACE'OS'BOOL_OP;OR;COMPOSITE_TEST;<Unused>;CASE_INSENSITIVE_TEST @Value(ZONE_TTL) CONTAINS Commercial'C'BOOL_OP;OR;COMPOSITE_TEST;<Unused>;CASE_INSENSITIVE_TEST @Value(ZONE_TTL) CONTAINS Industrial'I'BOOL_OP;OR;COMPOSITE_TEST;<Unused>;CASE_INSENSITIVE_TEST @Value(ZONE_TTL) CONTAINS Residential'R'BOOL_OP;OR;COMPOSITE_TEST;<Unused>;TEST @Value(ZONE_TTL) = No Zone'NZ'BOOL_OP;OR;COMPOSITE_TEST;<Unused>;CASE_INSENSITIVE_TEST @Value(ZONE_TTL) CONTAINS Rural'RU'FME_NUM_CONDITIONS7___
    -> AttributeKeeper_4
AttributeKeeper_4
    KEEP_ATTRS = ZONE_TTL,LU_Code,City
    -> NullAttributeMapper
NullAttributeMapper
    ATTRCHOICE = All Attributes
    NULL_TREATMENT = Empty String
    SOURCE_ATTR_VAL = Null
    -> AttributeRenamer_4
AttributeRenamer_4
    ATTR_TABLE:
      RENAME_SET_DEFAULT ZONE2_ABR > LU_Code
      RENAME_SET_DEFAULT ZONE_TTL > LU_Desc
    -> AttributeManager_10
AttributeManager_10
    ATTR_TABLE:
      SET_TO LU_Code_alias = Landuse
      SET_TO LU_Desc_alias = Description
    -> Tester_24
    -> Tester_23
    -> Tester_20
    -> Tester_21
    -> Tester_17
    -> Tester_19
Tester_19
    BOOL_OP = OR
    TEST_CLAUSE = CASE_INSENSITIVE_TEST @Value(LU_Desc) CONTAINS Commercial
    PASSED -> Dissolver
Tester_17
    BOOL_OP = OR
    TEST_CLAUSE = CASE_INSENSITIVE_TEST @Value(LU_Desc) CONTAINS Open Space
    PASSED -> Dissolver_5
Tester_21
    BOOL_OP = OR
    TEST_CLAUSE = CASE_INSENSITIVE_TEST @Value(LU_Desc) CONTAINS Residential
    PASSED -> Dissolver_8
Tester_20
    BOOL_OP = OR
    TEST_CLAUSE = CASE_INSENSITIVE_TEST @Value(LU_Desc) CONTAINS Industrial
    PASSED -> Dissolver_9
Tester_23
    BOOL_OP = OR
    TEST_CLAUSE = CASE_INSENSITIVE_TEST @Value(LU_Desc) CONTAINS No Zone
    PASSED -> AttributeKeeper_8
AttributeKeeper_8
    KEEP_ATTRS = City,LU_Desc
    -> Dissolver_10
Dissolver_10
    ACCUM_INPUT_ATTRS = Use Attributes From One Feature
    CLEANING_TOLERANCE = None
    CONNECT_Z_MODE = First Wins
    DEAGGREGATE_INPUT = Yes
    GROUP_BY = LU_Desc
    NO_OVRLP = No
    AREA -> No_Zone (writer GEODATABASE_FILE_2)
No_Zone (writer GEODATABASE_FILE_2)
    attributes: LU_Desc char(200), City char(200)
Tester_24
    BOOL_OP = OR
    TEST_CLAUSE = CASE_INSENSITIVE_TEST @Value(LU_Desc) CONTAINS Rural
    PASSED -> AttributeKeeper_9
AttributeKeeper_9
    KEEP_ATTRS = LU_Code,City,LU_Desc
    -> Dissolver_11
Dissolver_11
    ACCUM_INPUT_ATTRS = Use Attributes From One Feature
    CLEANING_TOLERANCE = None
    CONNECT_Z_MODE = First Wins
    DEAGGREGATE_INPUT = Yes
    GROUP_BY = LU_Desc
    NO_OVRLP = No
    AREA -> Rural (writer GEODATABASE_FILE_2)
Rural (writer GEODATABASE_FILE_2)
    attributes: LU_Desc char(200), City char(200), LU_Code char(200)
zoning-bylaw-7069-humberstone (reader ESRISHAPE_4)
    attributes: ID number(18,0), OBJECTID number(18,0), B7069_ID char(32), BYLAW char(32), ZONE_TTL char(50), STREET char(25), LOCATION char(30), BYLAW_NO1 char(12), AMEND_NO1 char(12), SPEC_PROV1 char(12), BYLAW_NO2 char(12), AMEND_NO2 char(12), SPEC_PROV2 char(12), BYLAW_NO3 char(12), AMEND_NO3 char(12), BYLAW_NO_L char(15), TypeI number(18,0), BranchesI number(18,0), Coordinate number(18,0), XI double, YI double, LongitudeI double, LatitudeI double, LengthI double, AreaI double, BearingI double, SelectionM number(18,0), SelectionI logical, VersionI number(18,0)
    -> CoordinateSystemSetter_3
CoordinateSystemSetter_3
    COORDSYS = EPSG:26917
    -> AttributeCreator_5
AttributeCreator_5
    ATTR_TABLE:
      SET_TO City = Niagara Falls
      SET_TO LU_Code = A
    -> AttributeKeeper_5
AttributeKeeper_5
    KEEP_ATTRS = LU_Code,City,ZONE_TTL
    -> AttributeRenamer_5
AttributeRenamer_5
    ATTR_TABLE = RENAME_SET_DEFAULT ZONE_TTL > LU_Desc
    -> AttributeManager_11
AttributeManager_11
    ATTR_TABLE:
      SET_TO LU_Code_alias = Landuse
      SET_TO LU_Desc_alias = Description
    -> Dissolver_2
zoning-bylaw-79-200 (reader ESRISHAPE_6)
    attributes: ID number(18,0), OBJECTID number(18,0), B79200_ID number(18,0), COLOUR_COD number(18,0), BYLAW char(10), ZONE_ABR char(10), ZONE2_ABR char(10), ZONE_TYPE char(40), ZONE_TTL char(60), STREET char(40), LOCATION char(25), BYLAW_NO1 char(10), SPEC_PROV1 char(10), SP1 char(10), AMEND_NO1 char(15), Bylaw1_Lin char(80), BYLAW_NO2 char(10), SPEC_PROV2 char(15), SP2 char(10), AMEND_NO2 char(15), Bylaw2_Lin char(80), BYLAW_NO3 char(8), Spec_Prov3 char(10), AMEND_NO3 char(15), Bylaw3_Lin char(80), BYLAW_NO4 char(50), SPEC_PROV4 char(50), AMEND_NO4 char(50), Bylaw4_Lin char(80), Label char(254),
      EXPIRATION char(50), TypeI number(18,0), BranchesI number(18,0), Coordinate number(18,0), XI double, YI double, LongitudeI double, LatitudeI double, LengthI double, AreaI double, BearingI double, SelectionM number(18,0), SelectionI logical, VersionI number(18,0)
    -> CoordinateSystemSetter_4
CoordinateSystemSetter_4
    COORDSYS = EPSG:26917
    -> AttributeCreator_6
AttributeCreator_6
    ATTR_TABLE = SET_TO City = Niagara Falls
    -> AttributeKeeper_6
AttributeKeeper_6
    KEEP_ATTRS = OBJECTID,City,ZONE2_ABR,ZONE_TTL
    -> AttributeRenamer_6
AttributeRenamer_6
    ATTR_TABLE:
      RENAME_SET_DEFAULT ZONE2_ABR > LU_Code
      RENAME_SET_DEFAULT ZONE_TTL > LU_Desc
    -> AttributeManager_12
AttributeManager_12
    ATTR_TABLE:
      SET_TO LU_Code_alias = Landuse
      SET_TO LU_Desc_alias = Description
    -> Tester_27
    -> Tester_31
    -> Tester_29
    -> AttributeManager
    -> Tester_30
    -> Tester_26
    -> Tester_28
Tester_29
    BOOL_OP = OR
    TEST_CLAUSE:
      CASE_INSENSITIVE_TEST @Value(LU_Code) CONTAINS OS
      TEST @Value(LU_Code) = EPA
    PASSED -> Dissolver_5
Dissolver_5
    ACCUM_INPUT_ATTRS = Use Attributes From One Feature
    CLEANING_TOLERANCE = None
    CONNECT_Z_MODE = First Wins
    DEAGGREGATE_INPUT = Yes
    GROUP_BY = LU_Desc
    NO_OVRLP = No
    AREA -> GreenSpace (writer GEODATABASE_FILE_1)
GreenSpace (writer GEODATABASE_FILE_1)
    attributes: LU_Code char(200), LU_Desc char(200), City char(200)
Tester_31
    BOOL_OP = OR
    TEST_CLAUSE = CASE_INSENSITIVE_TEST @Value(LU_Desc) CONTAINS AGRICULTURAL
    PASSED -> Dissolver_2
Dissolver_2
    ACCUM_INPUT_ATTRS = Use Attributes From One Feature
    CLEANING_TOLERANCE = None
    CONNECT_Z_MODE = First Wins
    DEAGGREGATE_INPUT = Yes
    GROUP_BY = LU_Desc
    NO_OVRLP = No
    AREA -> Agriculture (writer GEODATABASE_FILE_1)
Agriculture (writer GEODATABASE_FILE_1)
    attributes: LU_Code char(200), LU_Desc char(200), City char(200)
Tester_27
    BOOL_OP = OR
    TEST_CLAUSE = CASE_INSENSITIVE_TEST @Value(LU_Desc) CONTAINS COMMERCIAL
    PASSED -> Dissolver
Dissolver
    ACCUM_INPUT_ATTRS = Use Attributes From One Feature
    CLEANING_TOLERANCE = None
    CONNECT_Z_MODE = First Wins
    DEAGGREGATE_INPUT = Yes
    GROUP_BY = LU_Desc
    NO_OVRLP = No
    AREA -> Commercial (writer GEODATABASE_FILE_1)
Commercial (writer GEODATABASE_FILE_1)
    attributes: City char(200), LU_Code char(200), LU_Desc char(200)
Tester_30
    BOOL_OP = OR
    TEST_CLAUSE = CASE_INSENSITIVE_TEST @Value(LU_Desc) CONTAINS INSTITUTIONAL
    PASSED -> Dissolver_6
Dissolver_6
    ACCUM_INPUT_ATTRS = Use Attributes From One Feature
    CLEANING_TOLERANCE = None
    CONNECT_Z_MODE = First Wins
    DEAGGREGATE_INPUT = Yes
    GROUP_BY = LU_Desc
    NO_OVRLP = No
    AREA -> Institutional (writer GEODATABASE_FILE_1)
Institutional (writer GEODATABASE_FILE_1)
    attributes: City char(200), LU_Code char(200), LU_Desc char(200)
AttributeManager
    ATTR_TABLE = SET_TO LU_Code = R
    -> Tester_25
Tester_25
    BOOL_OP = OR
    TEST_CLAUSE = CASE_INSENSITIVE_TEST @Value(LU_Desc) CONTAINS RESIDENTIAL
    PASSED -> Dissolver_8
Dissolver_8
    ACCUM_INPUT_ATTRS = Use Attributes From One Feature
    CLEANING_TOLERANCE = None
    CONNECT_Z_MODE = First Wins
    DEAGGREGATE_INPUT = Yes
    GROUP_BY = LU_Desc
    NO_OVRLP = No
    AREA -> NullAttributeMapper_2
NullAttributeMapper_2
    ATTRCHOICE = Selected Attributes
    ATTRLIST = LU_Desc_alias LU_Desc LU_Code City OBJECTID LU_Code_alias
    NULL_TREATMENT = Missing
    OTHER_VALUE = 0
    SOURCE_ATTR_VAL = Null
    -> Residential (writer GEODATABASE_FILE_1)
Residential (writer GEODATABASE_FILE_1)
    attributes: City char(200), LU_Code char(200), LU_Desc char(200)
Tester_26
    BOOL_OP = OR
    TEST_CLAUSE = CASE_INSENSITIVE_TEST @Value(LU_Desc) CONTAINS INDUSTRIAL
    PASSED -> Dissolver_9
Dissolver_9
    ACCUM_INPUT_ATTRS = Use Attributes From One Feature
    CLEANING_TOLERANCE = None
    CONNECT_Z_MODE = First Wins
    DEAGGREGATE_INPUT = Yes
    GROUP_BY = LU_Desc
    NO_OVRLP = No
    AREA -> Industrial (writer GEODATABASE_FILE_2)
Industrial (writer GEODATABASE_FILE_2)
    attributes: City char(200), LU_Desc char(200), LU_Code char(200)
Tester_28
    BOOL_OP = OR
    TEST_CLAUSE = TEST @Value(LU_Code) = P
    PASSED -> AttributeKeeper_10
AttributeKeeper_10
    KEEP_ATTRS = LU_Code,City,LU_Desc
    -> Dissolver_12
Dissolver_12
    ACCUM_INPUT_ATTRS = Use Attributes From One Feature
    CLEANING_TOLERANCE = None
    CONNECT_Z_MODE = First Wins
    DEAGGREGATE_INPUT = Yes
    GROUP_BY = LU_Desc
    NO_OVRLP = No
    AREA -> Utility (writer GEODATABASE_FILE_2)
Utility (writer GEODATABASE_FILE_2)
    attributes: City char(200), LU_Code char(200), LU_Desc char(200)

Bookmark: Demographics and Boundaries
Schools (reader ESRISHAPE_7)
    attributes: School_Nam char(254), Municipali char(30), Phone_No char(15), School_Boa char(254), School_Typ char(254), Grade char(50), Full_Addre char(100), Nutrition_ char(10)
    -> CoordinateSystemSetter_5
CoordinateSystemSetter_5
    COORDSYS = EPSG:26917
    -> AttributeRenamer_7
AttributeRenamer_7
    ATTR_TABLE:
      RENAME_SET_DEFAULT Full_Addre > Address
      RENAME_SET_DEFAULT Municipali > Municipality
      RENAME_SET_DEFAULT Nutrition_ > Nutrition
      RENAME_SET_DEFAULT School_Boa > Board
      RENAME_SET_DEFAULT School_Nam > Name
      RENAME_SET_DEFAULT School_Typ > Type
    -> Tester_33
Tester_33
    BOOL_OP = OR
    TEST_CLAUSE:
      TEST @Value(Municipality) = St. Catharines
      TEST @Value(Municipality) = Welland
      TEST @Value(Municipality) = Niagara Falls
      TEST @Value(Municipality) = Grimsby
    PASSED -> Schools (writer GEODATABASE_FILE_1)
Schools (writer GEODATABASE_FILE_1)
    attributes: Address char(200), Municipality char(200), Nutrition char(200), Board char(200), Name char(200), Type char(200), Phone_No char(15), Grade char(50)
UAB (reader ESRISHAPE_8)
    attributes: NAME char(50), TYPE char(50), Hectares long
    -> CoordinateSystemSetter_6
CoordinateSystemSetter_6
    COORDSYS = EPSG:26917
    -> AttributeRenamer_8
AttributeRenamer_8
    ATTR_TABLE:
      RENAME_SET_DEFAULT Hectares > Area_Hect
      RENAME_SET_DEFAULT NAME > City
      RENAME_SET_DEFAULT TYPE > Type
    -> Tester_32
Tester_32
    BOOL_OP = OR
    TEST_CLAUSE:
      TEST @Value(City) = St. Catharines
      TEST @Value(City) = Welland
      TEST @Value(City) = Niagara Falls
      TEST @Value(City) = Grimsby
    PASSED -> AttributeManager_5
AttributeManager_5
    ATTR_TABLE = SET_TO Area_Hect_alias = Area in Hectares
    -> UrbanAreaBoundaries (writer GEODATABASE_FILE_1)
UrbanAreaBoundaries (writer GEODATABASE_FILE_1)
    attributes: Area_Hect char(200), City char(200), Type char(200)
PublicTransitRoutes (reader ESRISHAPE_9)
    attributes: Route_Name char(100), Accessible char(3), Service_Da char(100), ServiceCat char(50), ServiceAre char(50), Agency char(50), Shape_STLe number(31,15)
    -> CoordinateSystemSetter_7
CoordinateSystemSetter_7
    COORDSYS = EPSG:26917
    -> AttributeRenamer_9
AttributeRenamer_9
    ATTR_TABLE:
      RENAME_SET_DEFAULT Service_Da > Service_Days
      RENAME_SET_DEFAULT ServiceAre > Service_Area
      RENAME_SET_DEFAULT ServiceCat > Service_Category
    -> AttributeManager_2
AttributeManager_2
    ATTR_TABLE:
      SET_TO Service_Days_alias = Service Days
      SET_TO Route_Name_alias = Route Name
      SET_TO Service_Area_alias = Service Area
      SET_TO Service_Category_alias = Service Category
      SET_TO Shape_STLe_alias = Rout Length (Metres)
    -> TransitRoutes (writer GEODATABASE_FILE_1)
TransitRoutes (writer GEODATABASE_FILE_1)
    attributes: Service_Days char(200), Service_Area char(200), Service_Category char(200), Route_Name char(100), Accessible char(3), Agency char(50), Shape_STLe integer
MunicipalBoundaries (reader ESRISHAPE_11)
    attributes: Name char(68), POP2016 number(11,0), LandArea long, Mayor char(50), Label char(100)
    -> FeatureMerger [REQUESTOR]
CSV (reader CSV2_1)
    attributes: City string, AgeBelow14 string, AgeOver65 string, AgeOver85 string, Age15to64 string, Income10Kto50K string, Income50Kto100K string, Income100Kto150K string, IncomeOver150K string, IncomeUnder10K string
    -> FeatureMerger [SUPPLIER]
FeatureMerger
    ATTR_ACCUM_MODE = Merge Supplier
    ATTR_CONFLICT_RES = Use Requestor
    IGNORE_NULLS = No
    JOIN_KEYS = @Value(Name) @Value(City) AUTO
    MERGE_TYPE = Attributes and Geometry
    PROCESS_DUPS = NO
    REJECT_NULL_MISSING_KEYS = No
    SUPPLIERS_FIRST = No
    MERGED -> CoordinateSystemSetter_9
CoordinateSystemSetter_9
    COORDSYS = EPSG:26917
    -> MunicipalBoundaries (writer GEODATABASE_FILE_1)
MunicipalBoundaries (writer GEODATABASE_FILE_1)
    attributes: Name char(68), POP2016 double(11,0), LandArea integer, Mayor char(50), Label char(100), City char(15), AgeBelow14 double(20,10), Age15to64 double(20,10), AgeOver65 double(20,10), AgeOver85 double(20,10), IncomeUnder10K double, Income10Kto50K double, Income50Kto100K double, Income100Kto150K double, IncomeOver150K double

Bookmark: Welland
Welland_current_zoning_by-law_2017-117 (reader ESRISHAPE_2)
    attributes: ID number(18,0), Zoning2016 char(50), Zone_doc char(150)
    -> AttributeRenamer_3
AttributeRenamer_3
    ATTR_TABLE = RENAME_SET_DEFAULT Zoning2016 > LU_Code
    -> AttributeCreator
AttributeCreator
    ATTR_TABLE:
      SET_TO City = Welland
      SET_TO LU_Desc = FME_CONDITIONAL:DEFAULT_VALUE'_FME_NO_OP_'BOOL_OP;OR;COMPOSITE_TEST;<Unused>;TEST @Value(LU_Code) = L1'Light Industrial'BOOL_OP;OR;COMPOSITE_TEST;<Unused>;TEST @Value(LU_Code) = G1'General Industrial'BOOL_OP;OR;COMPOSITE_TEST;<Unused>;TEST @Value(LU_Code) = GEC'Gateway Economic Centre'BOOL_OP;OR;COMPOSITE_TEST;<Unused>;TEST @Value(LU_Code) = X'Aggregate Extraction'BOOL_OP;OR;COMPOSITE_TEST;<Unused>;TEST @Value(LU_Code) = A1'Agricultural'BOOL_OP;OR;COMPOSITE_TEST;<Unused>;TEST @Value(LU_Code) = RR'Rural Residential'BOOL_OP;OR;COMPOSITE_TEST;<Unused>;TEST @Value(LU_Code) = RE'Rural Employment'BOOL_OP;OR;COMPOSITE_TEST;<Unused>;TEST @Value(LU_Code) = RT'Railway Transportation'BOOL_OP;OR;COMPOSITE_TEST;<Unused>;TEST @Value(LU_Code) = INSH'Health and Wellness'BOOL_OP;OR;COMPOSITE_TEST;<Unused>;TEST @Value(LU_Code) = INS1'Community Institutional'BOOL_OP;OR;COMPOSITE_TEST;<Unused>;TEST @Value(LU_Code) = RL1'Residential Low Density 1'BOOL_OP;OR;COMPOSITE_TEST;<Unused>;TEST @Value(LU_Code) = RL2'Residential Low Density 2'BOOL_OP;OR;COMPOSITE_TEST;<Unused>;TEST @Value(LU_Code) = RM'Residential Medium Density'BOOL_OP;OR;COMPOSITE_TEST;<Unused>;TEST @Value(LU_Code) = RH'Residential High Density'BOOL_OP;OR;COMPOSITE_TEST;<Unused>;TEST @Value(LU_Code) = DMC'Downtown Mixed Use Centre'BOOL_OP;OR;COMPOSITE_TEST;<Unused>;TEST @Value(LU_Code) = RS'Regional Shopping Node'BOOL_OP;OR;COMPOSITE_TEST;<Unused>;TEST @Value(LU_Code) = CC1'Community Commercial Node'BOOL_OP;OR;COMPOSITE_TEST;<Unused>;TEST @Value(LU_Code) = CC2'Community Commercial Corridor'BOOL_OP;OR;COMPOSITE_TEST;<Unused>;TEST @Value(LU_Code) = NC'Neighbourhood Commercial'BOOL_OP;OR;COMPOSITE_TEST;<Unused>;TEST @Value(LU_Code) = O1'Neighbourhood Open Space'BOOL_OP;OR;COMPOSITE_TEST;<Unused>;TEST @Value(LU_Code) = O2'Community Open Space'BOOL_OP;OR;COMPOSITE_TEST;<Unused>;TEST @Value(LU_Code) = WRW'Welland Recreational Waterway'BOOL_OP;OR;COMPOSITE_TEST;<Unused>;TEST @Value(LU_Code) = HA'Hazard Overlay'BOOL_OP;OR;COMPOSITE_TEST;<Unused>;TEST @Value(LU_Code) = EP'Environmental Protection Overlay'BOOL_OP;OR;COMPOSITE_TEST;<Unused>;TEST @Value(LU_Code) = EC'Environmental Conservation Overlay'FME_NUM_CONDITIONS26___
    -> AttributeKeeper_2
AttributeKeeper_2
    KEEP_ATTRS = LU_Code,LU_Desc,City
    -> AttributeManager_7
AttributeManager_7
    ATTR_TABLE:
      SET_TO LU_Code_alias = Landuse
      SET_TO LU_Desc_alias = Description
    -> Commercial_4
    -> Agriculture_2
    -> Conservation_Natural_Area_2
    -> Green_Space_2
    -> Institutional_3
    -> Residential_3
    -> Industrial
Commercial_4: Tester
    BOOL_OP = OR
    TEST_CLAUSE:
      TEST @Value(LU_Code) = DMC
      TEST @Value(LU_Code) = RS
      TEST @Value(LU_Code) = CC1
      TEST @Value(LU_Code) = CC2
      TEST @Value(LU_Code) = NC
    PASSED -> Dissolver
Agriculture_2: Tester
    BOOL_OP = OR
    TEST_CLAUSE = TEST @Value(LU_Code) = A1
    PASSED -> Dissolver_2
Conservation_Natural_Area_2: Tester
    BOOL_OP = OR
    TEST_CLAUSE:
      TEST @Value(LU_Code) = HA
      TEST @Value(LU_Code) = EP
      TEST @Value(LU_Code) = EC
    PASSED -> Dissolver_4
Green_Space_2: Tester
    BOOL_OP = OR
    TEST_CLAUSE:
      TEST @Value(LU_Code) = O1
      TEST @Value(LU_Code) = O2
      TEST @Value(LU_Code) = WRW
    PASSED -> Dissolver_5
Institutional_3: Tester
    BOOL_OP = OR
    TEST_CLAUSE:
      TEST @Value(LU_Code) = INS1
      TEST @Value(LU_Code) = INSH
    PASSED -> Dissolver_6
Residential_3: Tester
    BOOL_OP = OR
    TEST_CLAUSE:
      TEST @Value(LU_Code) = RL1
      TEST @Value(LU_Code) = RL2
      TEST @Value(LU_Code) = RM
      TEST @Value(LU_Code) = RH
    PASSED -> Dissolver_8
Industrial: Tester
    BOOL_OP = OR
    TEST_CLAUSE:
      TEST @Value(LU_Code) = L1
      TEST @Value(LU_Code) = G1
      TEST @Value(LU_Code) = GEC
      TEST @Value(LU_Code) = X
    PASSED -> Dissolver_9
